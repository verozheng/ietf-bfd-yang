/*
 * This module has been generated by smidump 0.4.5:
 *
 *      smidump -f yang BFD-STD-MIB
 *
 * Do not edit. Edit the source file instead!
 */

module BFD-STD-MIB {

  /*** NAMESPACE / PREFIX DEFINITION ***/

  namespace "urn:ietf:params:xml:ns:yang:smiv2:BFD-STD-MIB";
  prefix "bfd-std";

  /*** LINKAGE (IMPORTS / INCLUDES) ***/

  import BFD-TC-STD-MIB      { prefix "bfd-tc"; }
  import DIFFSERV-MIB        { prefix "diffserv-mib"; }
  import IANA-BFD-TC-STD-MIB { prefix "iana-bfd"; }
  import IF-MIB              { prefix "if-mib"; }
  import INET-ADDRESS-MIB    { prefix "inet-address"; }
  import SNMPv2-TC           { prefix "smiv2"; }
  import ietf-yang-types          { prefix "yang"; }

  /*** META INFORMATION ***/

  organization      
   "IETF Bidirectional Forwarding Detection
    Working Group";

  contact           
   "Thomas D. Nadeau
    Brocade
    Email:  tnadeau@lucidvision.com
    
    Zafar Ali
    Cisco Systems, Inc.
    Email:  zali@cisco.com
    
    Nobo Akiya
    Cisco Systems, Inc.
    Email:  nobo@cisco.com
    
    Comments about this document should be emailed
    directly to the BFD Working Group mailing list
    at rtg-bfd@ietf.org";

  description       
   "Bidirectional Forwarding Management Information Base.
    
    Copyright (c) 2014 IETF Trust and the persons identified
    as authors of the code.  All rights reserved.
    
    Redistribution and use in source and binary forms, with
    or without modification, is permitted pursuant to, and
    subject to the license terms contained in, the Simplified
    BSD License set forth in Section 4.c of the IETF Trust's
    Legal Provisions Relating to IETF Documents
    (http://trustee.ietf.org/license-info).";

  revision "2014-08-12" {
    description     
     "Initial version.  Published as RFC 7331.";
  }

  container bfdObjects {


    /* XXX table comments here XXX */

    list bfdSessEntry {

      key "bfdSessIndex";
      description   
       "The BFD Session Entry describes the BFD session.";


      leaf bfdSessIndex {
        type bfd-tc:BfdSessIndexTC;
        config false;
        description 
         "This object contains an index used to represent a
          unique BFD session on this device.  Managers
          should obtain new values for row creation in this
          table by reading bfdSessIndexNext.";
      }

      leaf bfdSessVersionNumber {
        type uint32 {
          range "0..7";
        }
        config true;
        description 
         "The version number of the BFD protocol that this session
          is running in.  Write access is available for this object
          to provide the ability to set the desired version for this
          BFD session.";
        reference   
         "RFC 5880, Bidirectional Forwarding Detection (BFD).";
      }

      leaf bfdSessType {
        type iana-bfd:IANAbfdSessTypeTC;
        config true;
        description 
         "This object specifies the type of this BFD session.";
      }

      leaf bfdSessDiscriminator {
        type uint32 {
          range "1..4294967295";
        }
        config true;
        description 
         "This object specifies the local discriminator for this BFD
          session, which is used to uniquely identify it.";
      }

      leaf bfdSessRemoteDiscr {
        type uint32 {
          range "0..4294967295";
        }
        config false;
        description 
         "This object specifies the session discriminator chosen
          by the remote system for this BFD session.  The value may
          be zero(0) if the remote discriminator is not yet known
          or if the session is in the down or adminDown(1) state.";
        reference   
         "Section 6.8.6 of RFC 5880, Bidirectional
          Forwarding Detection (BFD).";
      }

      leaf bfdSessDestinationUdpPort {
        type bfd-tc:BfdCtrlDestPortNumberTC;
        config true;
        description 
         "This object specifies the destination UDP port number
          used for this BFD session's Control packets.  The value
          may be zero(0) if the session is in adminDown(1) state.";
      }

      leaf bfdSessSourceUdpPort {
        type bfd-tc:BfdCtrlSourcePortNumberTC;
        config true;
        description 
         "This object specifies the source UDP port number used
          for this BFD session's Control packets.  The value may be
          zero(0) if the session is in adminDown(1) state.  Upon
          creation of a new BFD session via this MIB, the value of
          zero(0) specified would permit the implementation to
          choose its own source port number.";
      }

      leaf bfdSessEchoSourceUdpPort {
        type inet-address:InetPortNumber;
        config true;
        description 
         "This object specifies the source UDP port number used for
          this BFD session's Echo packets.  The value may be zero(0)
          if the session is not running in the Echo mode, or the
          session is in adminDown(1) state.  Upon creation of a new
          BFD session via this MIB, the value of zero(0) would
          permit the implementation to choose its own source port
          number.";
      }

      leaf bfdSessAdminStatus {
        type enumeration {
          enum enabled   { value 1; }
          enum disabled  { value 2; }
          enum adminDown { value 3; }
          enum down      { value 4; }
        }
        config true;
        description 
         "Denotes the desired operational status of the BFD session.
          
          A transition to enabled(1) will start the BFD state machine
          for the session.  The state machine will have an initial
          state of down(2).
          
          A transition to disabled(2) will stop the BFD state machine
          for the session.  The state machine may first transition to
          adminDown(1) prior to stopping.
          
          A transition to adminDown(3) will cause the BFD state
          machine to transition to adminDown(1) and will cause the
          session to remain in this state.
          
          A transition to down(4) will cause the BFD state machine
          to transition to down(2) and will cause the session to
          remain in this state.
          
          Care should be used in providing write access to this
          object without adequate authentication.";
      }

      leaf bfdSessOperStatus {
        type enumeration {
          enum up        { value 1; }
          enum down      { value 2; }
          enum adminDown { value 3; }
        }
        config false;
        description 
         "Denotes the actual operational status of the BFD session.
          If the value of bfdOperStatus is down(2), this value MUST
          eventually be down(2) as well.  If the value of
          bfdOperStatus is adminDown(3), this value MUST eventually
          be adminDown(3) as well.";
      }

      leaf bfdSessState {
        type iana-bfd:IANAbfdSessStateTC;
        config false;
        description 
         "Configured BFD session state.";
      }

      leaf bfdSessRemoteHeardFlag {
        type smiv2:TruthValue;
        config false;
        description 
         "This object specifies the status of BFD packet reception from
          the remote system.  Specifically, it is set to true(1) if
          the local system is actively receiving BFD packets from the
          remote system and is set to false(2) if the local system
          has not received BFD packets recently (within the detection
          time) or if the local system is attempting to tear down
          the BFD session.";
        reference   
         "RFC 5880, Bidirectional Forwarding Detection (BFD).";
      }

      leaf bfdSessDiag {
        type iana-bfd:IANAbfdDiagTC;
        config false;
        description 
         "A diagnostic code specifying the local system's reason
          for the last transition of the session from up(4)
          to some other state.";
      }

      leaf bfdSessOperMode {
        type iana-bfd:IANAbfdSessOperModeTC;
        config true;
        description 
         "This object specifies the operational mode of this
          BFD session.";
      }

      leaf bfdSessDemandModeDesiredFlag {
        type smiv2:TruthValue;
        config true;
        description 
         "This object indicates the local system's
          desire to use Demand mode.  Specifically, it is set
          to true(1) if the local system wishes to use
          Demand mode or false(2) if not.";
      }

      leaf bfdSessControlPlaneIndepFlag {
        type smiv2:TruthValue;
        config true;
        description 
         "This object indicates the local system's
          ability to continue to function through a disruption of
          the control plane.  Specifically, it is set
          to true(1) if the local system BFD implementation is
          independent of the control plane.  Otherwise, the
          value is set to false(2).";
      }

      leaf bfdSessMultipointFlag {
        type smiv2:TruthValue;
        config true;
        description 
         "This object indicates the Multipoint (M) bit for this
          session.  It is set to true(1) if the Multipoint (M) bit is
          set to 1.  Otherwise, the value is set to false(2).";
      }

      leaf bfdSessInterface {
        type if-mib:InterfaceIndexOrZero;
        config true;
        description 
         "This object contains an interface index used to indicate
          the interface that this BFD session is running on.  This
          value can be zero if there is no interface associated
          with this BFD session.";
      }

      leaf bfdSessSrcAddrType {
        type inet-address:InetAddressType;
        config true;
        description 
         "This object specifies the IP address type of the source IP
          address of this BFD session.  The value of unknown(0) is
          allowed only when the session is singleHop(1) and the
          source IP address of this BFD session is derived from
          the outgoing interface, or when the BFD session is not
          associated with a specific interface.  If any other
          unsupported values are attempted in a set operation, the
          
          agent MUST return an inconsistentValue error.";
      }

      leaf bfdSessSrcAddr {
        type inet-address:InetAddress;
        config true;
        description 
         "This object specifies the source IP address of this BFD
          session.  The format of this object is controlled by the
          bfdSessSrcAddrType object.";
      }

      leaf bfdSessDstAddrType {
        type inet-address:InetAddressType;
        config true;
        description 
         "This object specifies the IP address type of the neighboring
          IP address that is being monitored with this BFD session.
          The value of unknown(0) is allowed only when the session is
          singleHop(1) and the outgoing interface is of type
          point to point, or when the BFD session is not associated
          with a specific interface.  If any other unsupported values
          are attempted in a set operation, the agent MUST return an
          inconsistentValue error.";
      }

      leaf bfdSessDstAddr {
        type inet-address:InetAddress;
        config true;
        description 
         "This object specifies the neighboring IP address that is
          being monitored with this BFD session.  The format of this
          object is controlled by the bfdSessDstAddrType object.";
      }

      leaf bfdSessGTSM {
        type smiv2:TruthValue;
        config true;
        description 
         "Setting the value of this object to false(2) will disable
          GTSM protection of the BFD session.  GTSM MUST be enabled
          on a singleHop(1) session if no authentication is in use.";
        reference   
         "RFC 5082, The Generalized TTL Security Mechanism (GTSM).
          Section 5 of RFC 5881, Bidirectional Forwarding Detection
          (BFD) for IPv4 and IPv6 (Single Hop).";
      }

      leaf bfdSessGTSMTTL {
        type uint32 {
          range "0..255";
        }
        config true;
        description 
         "This object is valid only when bfdSessGTSM protection is
          enabled on the system.  This object indicates the minimum
          allowed Time to Live (TTL) for received BFD Control packets.
          For a singleHop(1) session, if GTSM protection is enabled,
          this object SHOULD be set to the maximum TTL value allowed
          for a single hop.
          
          By default, GTSM is enabled and the TTL value is 255.  For a
          multihop session, updating of the maximum TTL value allowed
          is likely required.";
        reference   
         "RFC 5082, The Generalized TTL Security Mechanism (GTSM).
          Section 5 of RFC 5881, Bidirectional Forwarding Detection
          (BFD) for IPv4 and IPv6 (Single Hop).";
      }

      leaf bfdSessDesiredMinTxInterval {
        type bfd-tc:BfdIntervalTC;
        config true;
        description 
         "This object specifies the minimum interval, in
          microseconds, that the local system would like to use
          when transmitting BFD Control packets.  The value of
          zero(0) is reserved in this case and should not be
          used.";
        reference   
         "Section 4.1 of RFC 5880, Bidirectional Forwarding
          Detection (BFD).";
      }

      leaf bfdSessReqMinRxInterval {
        type bfd-tc:BfdIntervalTC;
        config true;
        description 
         "This object specifies the minimum interval, in
          microseconds, between received BFD Control packets the
          local system is capable of supporting.  The value of
          zero(0) can be specified when the transmitting system
          does not want the remote system to send any periodic BFD
          Control packets.";
        reference   
         "Section 4.1 of RFC 5880, Bidirectional Forwarding
          Detection (BFD).";
      }

      leaf bfdSessReqMinEchoRxInterval {
        type bfd-tc:BfdIntervalTC;
        config true;
        description 
         "This object specifies the minimum interval, in
          microseconds, between received BFD Echo packets that this
          system is capable of supporting.  The value must be zero(0) if
          this is a multihop BFD session.";
      }

      leaf bfdSessDetectMult {
        type bfd-tc:BfdMultiplierTC;
        config true;
        description 
         "This object specifies the Detect time multiplier.";
      }

      leaf bfdSessNegotiatedInterval {
        type bfd-tc:BfdIntervalTC;
        config false;
        description 
         "This object specifies the negotiated interval, in
          microseconds, that the local system is transmitting
          BFD Control packets.";
      }

      leaf bfdSessNegotiatedEchoInterval {
        type bfd-tc:BfdIntervalTC;
        config false;
        description 
         "This object specifies the negotiated interval, in
          microseconds, that the local system is transmitting
          BFD Echo packets.  The value is expected to be zero if
          the sessions are not running in Echo mode.";
      }

      leaf bfdSessNegotiatedDetectMult {
        type bfd-tc:BfdMultiplierTC;
        config false;
        description 
         "This object specifies the Detect time multiplier.";
      }

      leaf bfdSessAuthPresFlag {
        type smiv2:TruthValue;
        config true;
        description 
         "This object indicates the local system's
          desire to use authentication.  Specifically, it is set
          to true(1) if the local system wishes the session
          to be authenticated or false(2) if not.";
        reference   
         "Sections 4.2 - 4.4 of RFC 5880, Bidirectional Forwarding
          Detection (BFD).";
      }

      leaf bfdSessAuthenticationType {
        type iana-bfd:IANAbfdSessAuthenticationTypeTC;
        config true;
        description 
         "The authentication type used for this BFD session.
          This field is valid only when the Authentication
          Present bit is set.  MAX-ACCESS to this object as well as
          other authentication-related objects are set to
          read-create in order to support management of a single
          key ID at a time; key rotation is not handled.  Key update
          in practice must be done by atomic update using a set
          containing all affected objects in the same varBindList
          or otherwise risk the session dropping.";
        reference   
         "Sections 4.2 - 4.4 of RFC 5880, Bidirectional Forwarding
          Detection (BFD).";
      }

      leaf bfdSessAuthenticationKeyID {
        type int32 {
          range "-1..255";
        }
        config true;
        description 
         "The authentication key ID in use for this session.  This
          object permits multiple keys to be active simultaneously.
          The value -1 indicates that no authentication key ID will
          be present in the optional BFD Authentication Section.";
        reference   
         "Sections 4.2 - 4.4 of RFC 5880, Bidirectional Forwarding
          Detection (BFD).";
      }

      leaf bfdSessAuthenticationKey {
        type iana-bfd:IANAbfdSessAuthenticationKeyTC;
        config true;
        description 
         "The authentication key.  When the
          bfdSessAuthenticationType is simplePassword(1), the value
          of this object is the password present in the BFD packets.
          
          When the bfdSessAuthenticationType is one of the keyed
          authentication types, this value is used in the
          computation of the key present in the BFD authentication
          packet.";
        reference   
         "Sections 4.2 - 4.4 of RFC 5880, Bidirectional Forwarding
          Detection (BFD).";
      }

      leaf bfdSessStorageType {
        type smiv2:StorageType;
        config true;
        description 
         "This variable indicates the storage type for this
          object.  Conceptual rows having the value
          'permanent' need not allow write-access to any
          columnar objects in the row.";
      }

      leaf bfdSessRowStatus {
        type smiv2:RowStatus;
        config true;
        description 
         "This variable is used to create, modify, and/or
          delete a row in this table.  When a row in this
          table has a row in the active(1) state, no
          objects in this row can be modified except the
          bfdSessRowStatus and bfdSessStorageType.";
      }
    }



    /* XXX table comments here XXX */

    list bfdSessDiscMapEntry {

      key "bfdSessDiscriminator";
      description   
       "The BFD Session Discriminator Mapping Entry
        specifies a mapping between a local discriminator
        and a BFD session.";

      leaf bfdSessDiscriminator {
        type keyref {
          path "/bfd-std:bfdObjects/bfd-std:bfdSessEntry/bfd-std:bfdSessDiscriminator";
        }
        config true;
        description 
         "Automagically generated keyref leaf.";
      }

      leaf bfdSessDiscMapIndex {
        type bfd-tc:BfdSessIndexTC;
        config false;
        description 
         "This object specifies a mapping between a
          local discriminator and a BFD session in
          the BfdSessTable.";
      }
    }


    /* XXX table comments here XXX */

    list bfdSessIpMapEntry {

      key "bfdSessInterface bfdSessSrcAddrType bfdSessSrcAddr 
           bfdSessDstAddrType bfdSessDstAddr";
      description   
       "The BFD Session IP Map Entry contains a mapping
        from the IP information for a session to the session
        in the bfdSessionTable.";

      leaf bfdSessInterface {
        type keyref {
          path "/bfd-std:bfdObjects/bfd-std:bfdSessEntry/bfd-std:bfdSessInterface";
        }
        config true;
        description 
         "Automagically generated keyref leaf.";
      }
      leaf bfdSessSrcAddrType {
        type keyref {
          path "/bfd-std:bfdObjects/bfd-std:bfdSessEntry/bfd-std:bfdSessSrcAddrType";
        }
        config true;
        description 
         "Automagically generated keyref leaf.";
      }
      leaf bfdSessSrcAddr {
        type keyref {
          path "/bfd-std:bfdObjects/bfd-std:bfdSessEntry/bfd-std:bfdSessSrcAddr";
        }
        config true;
        description 
         "Automagically generated keyref leaf.";
      }
      leaf bfdSessDstAddrType {
        type keyref {
          path "/bfd-std:bfdObjects/bfd-std:bfdSessEntry/bfd-std:bfdSessDstAddrType";
        }
        config true;
        description 
         "Automagically generated keyref leaf.";
      }
      leaf bfdSessDstAddr {
        type keyref {
          path "/bfd-std:bfdObjects/bfd-std:bfdSessEntry/bfd-std:bfdSessDstAddr";
        }
        config true;
        description 
         "Automagically generated keyref leaf.";
      }

      leaf bfdSessIpMapIndex {
        type bfd-tc:BfdSessIndexTC;
        config false;
        description 
         "This object specifies the BfdSessIndexTC referred
          to by the indexes of this row.  In essence, a mapping is
          provided between these indexes and the BfdSessTable.";
      }
    }
  }

  container bfdScalarObjects {

    leaf bfdAdminStatus {
      type enumeration {
        enum enabled   { value 1; }
        enum disabled  { value 2; }
        enum adminDown { value 3; }
        enum down      { value 4; }
      }
      config true;
      description   
       "The desired global administrative status of the
        BFD system in this device.";
    }

    leaf bfdOperStatus {
      type enumeration {
        enum up        { value 1; }
        enum down      { value 2; }
        enum adminDown { value 3; }
      }
      config false;
      description   
       "Indicates the actual operational status of the
        BFD system in this device.  When this value is
        down(2), all entries in the bfdSessTable MUST have
        their bfdSessOperStatus as down(2) as well.  When
        this value is adminDown(3), all entries in the
        bfdSessTable MUST have their bfdSessOperStatus
        as adminDown(3) as well.";
    }

    leaf bfdNotificationsEnable {
      type smiv2:TruthValue;
      config true;
      description   
       "If this object is set to true(1), then it enables
        the emission of bfdSessUp and bfdSessDown
        notifications; otherwise, these notifications are not
        emitted.";
      reference     
       "See also RFC 3413, Simple Network Management Protocol (SNMP)
        Applications, for explanation that
        notifications are under the ultimate control of the
        MIB modules in this document.";
    }

    leaf bfdSessIndexNext {
      type diffserv-mib:IndexIntegerNextFree {
        range "0..4294967295";
      }
      config false;
      description   
       "This object contains an unused value for
        bfdSessIndex that can be used when creating
        entries in the table.  A zero indicates that
        no entries are available, but it MUST NOT be used
        as a valid index. ";
    }
  }


  /* XXX table comments here XXX */

  augment "/bfd-std:bfdObjects/bfd-std:bfdSessEntry" {
    description     
     "An entry in this table is created by a BFD-enabled node
      for every BFD session. bfdSessPerfDiscTime is used to
      indicate potential discontinuity for all counter objects
      in this table.";

    leaf bfdSessPerfCtrlPktIn {
      type yang:counter32;
      config false;
      description   
       "The total number of BFD control messages received for this
        BFD session.
        
        It MUST be equal to the least significant 32 bits of
        bfdSessPerfCtrlPktInHC if supported, and MUST do so
        with the rules spelled out in RFC 2863.";
    }

    leaf bfdSessPerfCtrlPktOut {
      type yang:counter32;
      config false;
      description   
       "The total number of BFD control messages sent for this BFD
        session.
        
        It MUST be equal to the least significant 32 bits of
        bfdSessPerfCtrlPktOutHC if supported, and MUST do so
        with the rules spelled out in RFC 2863.";
    }

    leaf bfdSessPerfCtrlPktDrop {
      type yang:counter32;
      config false;
      description   
       "The total number of BFD control messages received for this
        session yet dropped for being invalid.
        
        It MUST be equal to the least significant 32 bits of
        bfdSessPerfCtrlPktDropHC if supported, and MUST do so
        with the rules spelled out in RFC 2863.";
    }

    leaf bfdSessPerfCtrlPktDropLastTime {
      type yang:timestamp;
      config false;
      description   
       "The value of sysUpTime on the most recent occasion at
        which received the BFD control message for this session was
        dropped.  If no such up event exists, this object contains
        a zero value.";
    }

    leaf bfdSessPerfEchoPktIn {
      type yang:counter32;
      config false;
      description   
       "The total number of BFD Echo messages received for this
        BFD session.
        
        It MUST be equal to the least significant 32 bits of
        bfdSessPerfEchoPktInHC if supported, and MUST do so
        with the rules spelled out in RFC 2863.";
    }

    leaf bfdSessPerfEchoPktOut {
      type yang:counter32;
      config false;
      description   
       "The total number of BFD Echo messages sent for this BFD
        session.
        
        It MUST be equal to the least significant 32 bits of
        bfdSessPerfEchoPktOutHC if supported, and MUST do so
        with the rules spelled out in RFC 2863.";
    }

    leaf bfdSessPerfEchoPktDrop {
      type yang:counter32;
      config false;
      description   
       "The total number of BFD Echo messages received for this
        session yet dropped for being invalid.
        
        It MUST be equal to the least significant 32 bits of
        bfdSessPerfEchoPktDropHC if supported, and MUST do so
        with the rules spelled out in RFC 2863.";
    }

    leaf bfdSessPerfEchoPktDropLastTime {
      type yang:timestamp;
      config false;
      description   
       "The value of sysUpTime on the most recent occasion at
        which received the BFD Echo message for this session was
        dropped.  If no such up event has been issued, this
        object contains a zero value.";
    }

    leaf bfdSessUpTime {
      type yang:timestamp;
      config false;
      description   
       "The value of sysUpTime on the most recent occasion at which
        the session came up.  If no such event has been issued,
        this object contains a zero value.";
    }

    leaf bfdSessPerfLastSessDownTime {
      type yang:timestamp;
      config false;
      description   
       "The value of sysUpTime on the most recent occasion at
        which the last time communication was lost with the
        neighbor.  If no down event has been issued, this object
        contains a zero value.";
    }

    leaf bfdSessPerfLastCommLostDiag {
      type iana-bfd:IANAbfdDiagTC;
      config false;
      description   
       "The BFD diag code for the last time communication was lost
        with the neighbor.  If such an event has not been issued,
        this object contains a zero value.";
    }

    leaf bfdSessPerfSessUpCount {
      type yang:counter32;
      config false;
      description   
       "The number of times this session has gone into the Up
        state since the system last rebooted.";
    }

    leaf bfdSessPerfDiscTime {
      type yang:timestamp;
      config false;
      description   
       "The value of sysUpTime on the most recent occasion at
        which any one or more of the session counters suffered
        a discontinuity.
        
        The relevant counters are the specific instances associated
        with this BFD session of any Counter32 object contained in
        the BfdSessPerfTable.  If no such discontinuities have
        occurred since the last reinitialization of the local
        management subsystem, then this object contains a zero
        value.";
    }

    leaf bfdSessPerfCtrlPktInHC {
      type yang:counter64;
      config false;
      description   
       "This value represents the total number of BFD control
        messages received for this BFD session.
        
        The least significant 32 bits MUST be equal to
        bfdSessPerfCtrlPktIn, and MUST do so with
        the rules spelled out in RFC 2863.";
    }

    leaf bfdSessPerfCtrlPktOutHC {
      type yang:counter64;
      config false;
      description   
       "This value represents the total number of BFD control
        messages transmitted for this BFD session.
        
        The least significant 32 bits MUST be equal to
        bfdSessPerfCtrlPktOut, and MUST do so with
        the rules spelled out in RFC 2863.";
    }

    leaf bfdSessPerfCtrlPktDropHC {
      type yang:counter64;
      config false;
      description   
       "This value represents the total number of BFD control
        messages received for this BFD session yet dropped for
        being invalid.
        
        The least significant 32 bits MUST be equal to
        bfdSessPerfCtrlPktDrop, and MUST do so with
        the rules spelled out in RFC 2863.";
    }

    leaf bfdSessPerfEchoPktInHC {
      type yang:counter64;
      config false;
      description   
       "This value represents the total number of BFD Echo
        messages received for this BFD session.
        
        The least significant 32 bits MUST be equal to
        bfdSessPerfEchoPktIn, and MUST do so with
        the rules spelled out in RFC 2863.";
    }

    leaf bfdSessPerfEchoPktOutHC {
      type yang:counter64;
      config false;
      description   
       "This value represents the total number of BFD Echo
        messages transmitted for this BFD session.
        
        The least significant 32 bits MUST be equal to
        bfdSessPerfEchoPktOut, and MUST do so with
        the rules spelled out in RFC 2863.";
    }

    leaf bfdSessPerfEchoPktDropHC {
      type yang:counter64;
      config false;
      description   
       "This value represents the total number of BFD Echo
        messages received for this BFD session yet dropped
        for being invalid.
        The least significant 32 bits MUST be equal to
        bfdSessPerfEchoPktDrop, and MUST do so with
        the rules spelled out in RFC 2863.";
    }
  }

  notification bfdSessUp {
    description     
     "This notification is generated when the
      bfdSessState object for one or more contiguous
      entries in bfdSessTable are about to enter the up(4)
      state from some other state.  The included values of
      bfdSessDiag MUST both be set equal to this
      new state (i.e., up(4)).  The two instances of
      bfdSessDiag in this notification indicate the range
      of indexes that are affected.  Note that all the indexes
      of the two ends of the range can be derived from the
      instance identifiers of these two objects.  For the
      cases where a contiguous range of sessions
      have transitioned into the up(4) state at roughly
      the same time, the device SHOULD issue a single
      notification for each range of contiguous indexes in
      an effort to minimize the emission of a large number
      of notifications.  If a notification has to be
      issued for just a single bfdSessEntry, then
      the instance identifier (and values) of the two
      bfdSessDiag objects MUST be identical.";

    container bfdSessUp-bfdSessDiag-1 {
      leaf bfdSessIndex {
        type keyref {
          path "/bfd-std:bfdObjects/bfd-std:bfdSessEntry/bfd-std:bfdSessIndex";
        }
        config true;
        description 
         "Automagically generated keyref leaf.";
      }
      leaf bfdSessDiag {
        type iana-bfd:IANAbfdDiagTC;
        config false;
        description 
         "A diagnostic code specifying the local system's reason
          for the last transition of the session from up(4)
          to some other state.";
      }
    }

    container bfdSessUp-bfdSessDiag-2 {
      leaf bfdSessIndex {
        type keyref {
          path "/bfd-std:bfdObjects/bfd-std:bfdSessEntry/bfd-std:bfdSessIndex";
        }
        config true;
        description 
         "Automagically generated keyref leaf.";
      }
      leaf bfdSessDiag {
        type iana-bfd:IANAbfdDiagTC;
        config false;
        description 
         "A diagnostic code specifying the local system's reason
          for the last transition of the session from up(4)
          to some other state.";
      }
    }

  }

  notification bfdSessDown {
    description     
     "This notification is generated when the
      bfdSessState object for one or more contiguous
      entries in bfdSessTable are about to enter the down(2)
      or adminDown(1) states from some other state.  The included
      values of bfdSessDiag MUST both be set equal to this new
      state (i.e., down(2) or adminDown(1)).  The two instances
      of bfdSessDiag in this notification indicate the range
      of indexes that are affected.  Note that all the indexes
      of the two ends of the range can be derived from the
      instance identifiers of these two objects.  For
      cases where a contiguous range of sessions
      have transitioned into the down(2) or adminDown(1) states
      at roughly the same time, the device SHOULD issue a single
      notification for each range of contiguous indexes in
      an effort to minimize the emission of a large number
      of notifications.  If a notification has to be
      issued for just a single bfdSessEntry, then
      the instance identifier (and values) of the two
      bfdSessDiag objects MUST be identical.";

    container bfdSessDown-bfdSessDiag-1 {
      leaf bfdSessIndex {
        type keyref {
          path "/bfd-std:bfdObjects/bfd-std:bfdSessEntry/bfd-std:bfdSessIndex";
        }
        config true;
        description 
         "Automagically generated keyref leaf.";
      }
      leaf bfdSessDiag {
        type iana-bfd:IANAbfdDiagTC;
        config false;
        description 
         "A diagnostic code specifying the local system's reason
          for the last transition of the session from up(4)
          to some other state.";
      }
    }

    container bfdSessDown-bfdSessDiag-2 {
      leaf bfdSessIndex {
        type keyref {
          path "/bfd-std:bfdObjects/bfd-std:bfdSessEntry/bfd-std:bfdSessIndex";
        }
        config true;
        description 
         "Automagically generated keyref leaf.";
      }
      leaf bfdSessDiag {
        type iana-bfd:IANAbfdDiagTC;
        config false;
        description 
         "A diagnostic code specifying the local system's reason
          for the last transition of the session from up(4)
          to some other state.";
      }
    }

  }
} /* end of module BFD-STD-MIB */
