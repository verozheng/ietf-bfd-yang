module ietf-bfd {
    namespace "urn:ietf:params:xml:ns:yang:bfd";
    prefix "bfd";

    organization "IETF BFD (Bidirectional Forwarding Detection) Working Group";
    contact 
        "WG Web:   <http://tools.ietf.org/wg/bfd/>
         WG List:  <mailto:rtg-bfd@ietf.org>

         WG Chair: ";

    description 
        "BFD Yang Module

         Copyright (c) 2014 IETF Trust and the persons identified as
         authors of the code.  All rights reserved.

         Redistribution and use in source and binary forms, with or
         without modification, is permitted pursuant to, and subject
         to the license terms contained in, the Simplified BSD License
         set forth in Section 4.c of the IETF Trust's Legal Provisions
         Relating to IETF Documents
         (http://trustee.ietf.org/license-info).

         This version of this YANG module is part of RFC XXXX; see
         the RFC itself for full legal notices.";

    revision 
        "2014-10-06" {
        description "Initial version";
    }

/*
 * typedefs
 */

/* 
 * configuration 
 */
    container bfd-config {
        description 
            "BFD configuration";

        leaf name {
            type string;
            description
                "A string that is used to identify the BFD session.";
        }

        leaf admin-state {
            description 
                "The adminstrative state of the BFD session";
            type enumeration {
                enum disable {
                    value "0";
                    description
                        "The administrative state of the session is disabled.";
		}
                enum enable {
                    value "1";
                    description
                        "The administrative state of the session is enabled";
                }
            }
	}

        leaf role {
            type enumeration {
                enum active {
                    description
                        "A system taking the Active role MUST send BFD
                        Control packets for a particular session, regardless of whether it
                        has received any BFD packets for that session";
                }

                enum passive {
                    description
                        "A system taking the Passive role MUST NOT begin sending BFD 
                         packets for a particular session until it has received a BFD 
                         packet for that session, and thus has learned the remote 
                         system's discriminator value.";
                }
            }
            description
                "Is this end the active or the passive end of the session. Note,
                 both ends can be active, but both ends cannot be passive.";
        }

        leaf version {
            type uint8 {
                range 0..7;
            }
            description
                "The version number of the protocol.";
        }

        leaf diag {
            type uint8 {
                range 0..31;
            }
            description
                "A diagnostic code specifying the local system's reason for the
                 last change in session state";
        }

        leaf state {
            type uint8 {
                range 0..3;
            }
            description
                "The current BFD session state as seen by the transmitting system.";
        }

        leaf bfd-bits {
            type bits {
                bit poll {
                    position 0;
                    description
                        "If set, the transmitting system is requesting verification of
                         connectivity, or of a parameter change, and is expecting a packet
                         with the Final (F) bit in reply.  If clear, the transmitting
                         system is not requesting verification.";
                }

                bit final {
                    position 1;
                    description
                        "If set, the transmitting system is responding to a received BFD
                         Control packet that had the Poll (P) bit set.  If clear, the
                         transmitting system is not responding to a Poll.";
                }

                bit control-plane-independent {
                    position 2;
                    description
                        "If set, the transmitting system's BFD implementation does not
                         share fate with its control plane (in other words, BFD is
                         implemented in the forwarding plane and can continue to function
                         through disruptions in the control plane).  If clear, the
                         transmitting system's BFD implementation shares fate with its
                         control plane.

                         The use of this bit is application dependent and is outside the
                         scope of this specification.  See specific application
                         specifications for details.";
                }

                bit authentication-present {
                    position 3;
                    description
                        "If set, the Authentication Section is present and the session is
                         to be authenticated (see section 6.7 for details).";
                }

                bit demand {
                    position 4;
                    description
                        "If set, Demand mode is active in the transmitting system (the
                         system wishes to operate in Demand mode, knows that the session is
                         Up in both directions, and is directing the remote system to cease
                         the periodic transmission of BFD Control packets).  If clear,
                         Demand mode is not active in the transmitting system.";
                }

                bit multipoint {
                    position 5;
                    description
                        "This bit is reserved for future point-to-multipoint extensions to
                         BFD.  It MUST be zero on both transmit and receipt.";
                }
            }
        }

        leaf detect-multiplier {
            type uint32;
            description
                "Detection time multiplier.  The negotiated transmit interval,
                 multiplied by this value, provides the Detection Time for the
                 receiving system in Asynchronous mode.";
        }

        leaf length {
            type uint32;
            description
                "Length of the BFD Control packet, in bytes.";
        }

        leaf my-discriminator {
            type uint32;
            description
                "A unique, nonzero discriminator value generated by the
                 transmitting system, used to demultiplex multiple BFD sessions
                 between the same pair of systems.";
        }

        leaf your-discriminator {
            type uint32;
            description
                "The discriminator received from the corresponding remote system.
                 This field reflects back the received value of My Discriminator,
                 or is zero if that value is unknown.";
        }

        leaf min-tx-interval {
            type uint32;
            description
                "This is the minimum interval, in microseconds, that the local
                 system would like to use when transmitting BFD Control packets,
                 less any jitter applied (see section 6.8.2).  The value zero is
                 reserved.";
        }

        leaf min-rx-interval {
            type uint32;
            description
                "This is the minimum interval, in microseconds, between received
                 BFD Control packets that this system is capable of supporting,
                 less any jitter applied by the sender (see section 6.8.2).  If
                 this value is zero, the transmitting system does not want the
                 remote system to send any periodic BFD Control packets.";
        }

        leaf min-rx-echo-interval {
            type uint32;
            description
                "This is the minimum interval, in microseconds, between received
                 BFD Echo packets that this system is capable of supporting, less
                 any jitter applied by the sender (see section 6.8.9).  If this
                 value is zero, the transmitting system does not support the
                 receipt of BFD Echo packets.";
        }

        leaf auth-type {
            type uint8;
            description
                "The authentication type in use, if the authentication-present
                 bit is set.";
        }

        leaf auth-length {
            type uint8;
            description
                "The length, in bytes, of the authentication section, including the
                 Auth Type and Auth Len fields.";
        }
    }
}
